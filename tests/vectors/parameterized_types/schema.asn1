-- =========================================================================
-- asnvil Test Vector: 1003_parameterized_types.asn1
-- Description: Referenced types with actual parameters
-- Attribution: Original asnvil test vector
-- =========================================================================

TestModule DEFINITIONS AUTOMATIC TAGS ::= BEGIN
    MyParamType ::= SEQUENCE { a INTEGER }
    MyRef ::= MyParamType { INTEGER }
END;
