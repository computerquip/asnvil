-- =========================================================================
-- asnvil Test Vector: 1002_named_numbers.asn1
-- Description: INTEGER named numbers with identifier references
-- Attribution: Original asnvil test vector
-- =========================================================================

TestModule DEFINITIONS AUTOMATIC TAGS ::= BEGIN
    MyInt ::= INTEGER { foo( Bar ), baz( 2 ) }
    NextType ::= BOOLEAN
END;
