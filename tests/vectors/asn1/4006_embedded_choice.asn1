-- =========================================================================
-- asnvil Test Vector: 4006_embedded_choice.asn1
-- Description: Embedded CHOICE types roundtrip
-- Attribution: Adapted from vlm/asn1c project (MIT license)
--              https://github.com/vlm/asn1c
-- =========================================================================

-- Embedded choice test module
-- Tests embedded CHOICE with AUTOMATIC TAGS

EmbeddedChoiceModule DEFINITIONS AUTOMATIC TAGS ::= BEGIN

EmbeddedChoice ::= CHOICE {
    integer     INTEGER,
    string      UTF8String,
    octet       OCTET STRING
}

Container ::= SEQUENCE {
    id      INTEGER,
    value   EmbeddedChoice
}

ExtendedSequence ::= SEQUENCE {
    name    UTF8String,
    value   INTEGER,
    extra   UTF8String OPTIONAL
}

END
;
