-- =========================================================================
-- asnvil Test Vector: 1001_value_items.asn1
-- Description: Sequence values with lowercase identifier keys
-- Attribution: Original asnvil test vector
-- =========================================================================

TestModule DEFINITIONS AUTOMATIC TAGS ::= BEGIN
    MyType ::= SEQUENCE {
        foo INTEGER,
        bar BOOLEAN
    }
    MyValue MyType ::= { foo: 1, bar: TRUE }
END;
