-- =========================================================================
-- asnvil Test Vector: 4004_recursive.asn1
-- Description: Recursive type definitions roundtrip
-- Attribution: Adapted from vlm/asn1c project (MIT license)
--              https://github.com/vlm/asn1c
-- =========================================================================

-- Recursive types test module
-- Tests recursive types (SET OF self, SEQUENCE OF self, recursive CHOICE)

RecursionModule DEFINITIONS AUTOMATIC TAGS ::= BEGIN

RecursiveSeq ::= SEQUENCE {
    value       INTEGER,
    children    SEQUENCE OF RecursiveSeq
}

RecursiveSet ::= SEQUENCE {
    value       INTEGER,
    children    SET OF RecursiveSet
}

RecursiveChoice ::= CHOICE {
    leaf        INTEGER,
    nested      RecursiveChoice
}

END
;
