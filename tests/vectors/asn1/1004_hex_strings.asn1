-- =========================================================================
-- asnvil Test Vector: 1004_hex_strings.asn1
-- Description: Valid and odd-length hex string literals
-- Attribution: Original asnvil test vector
-- =========================================================================

TestModule DEFINITIONS AUTOMATIC TAGS ::= BEGIN
    MyOctetValid OCTET STRING ::= 'DEADBEEF'H
    MyOctetOdd OCTET STRING ::= 'ABC'H
END;
