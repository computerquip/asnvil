-- =========================================================================
-- asnvil Test Vector: 1005_invalid_hex_string.asn1
-- Description: Invalid hex string literals (expected parse error)
-- Attribution: Original asnvil test vector
-- =========================================================================

TestModule DEFINITIONS AUTOMATIC TAGS ::= BEGIN
    MyOctetInvalid OCTET STRING ::= 'GHIJ'H
END;
