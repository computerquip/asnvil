-- =========================================================================
-- asnvil Test Vector: 3002_inline_choice.asn1
-- Description: Inline CHOICE types within SEQUENCE fields
-- Attribution: Adapted from vlm/asn1c project (MIT license)
--              https://github.com/vlm/asn1c
-- =========================================================================

-- Test ASN.1 file with inline CHOICE as SEQUENCE field
TestModule DEFINITIONS AUTOMATIC TAGS ::= BEGIN

    -- Inline CHOICE with tagged alternatives for distinguishability
    Person ::= SEQUENCE {
        name IA5String,
        age INTEGER,
        contact CHOICE {
            email [0] EXPLICIT IA5String,
            phone [1] EXPLICIT IA5String
        } OPTIONAL
    }

END;
