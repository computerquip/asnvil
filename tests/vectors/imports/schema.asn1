-- =========================================================================
-- asnvil Test Vector: 1000_imports.asn1
-- Description: Module imports, exports, and basic type assignments
-- Attribution: Original asnvil test vector
-- =========================================================================

TestModule DEFINITIONS AUTOMATIC TAGS ::= BEGIN
    EXPORTS MyType, AnotherType;
    IMPORTS INTEGER, SEQUENCE, OCTET FROM SpecModule;
    
    MyType ::= SEQUENCE {
        a INTEGER
    }
    AnotherType ::= BOOLEAN
END;
