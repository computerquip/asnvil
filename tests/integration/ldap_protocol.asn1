-- Simplified LDAP Protocol Module
-- Based on RFC 4511 LDAPv3 protocol specification
-- Simplified to work within current compiler capabilities

LDAPv3 DEFINITIONS IMPLICIT TAGS ::= BEGIN

MessageID ::= INTEGER

LDAPString ::= OCTET STRING

LDAPDN ::= LDAPString

AttributeName ::= LDAPString

AttributeValue ::= OCTET STRING

AttributeValueAssertion ::= SEQUENCE {
    attributeDesc   AttributeName,
    assertionValue  AttributeValue
}

PartialAttribute ::= SEQUENCE {
    typeAttr    AttributeName,
    vals        SET OF AttributeValue
}

LDAPResult ::= SEQUENCE {
    resultCode      ENUMERATED {
        success(0),
        operationsError(1),
        protocolError(2),
        timeLimitExceeded(3),
        sizeLimitExceeded(4),
        noSuchObject(32)
    },
    matchedDN       LDAPDN,
    diagnosticMessage LDAPString
}

PartialAttributeList ::= SEQUENCE OF PartialAttribute

SearchResultEntry ::= SEQUENCE {
    objectName  LDAPDN,
    attributes  PartialAttributeList
}

BindRequest ::= SEQUENCE {
    version         INTEGER,
    name            LDAPDN,
    authentication  OCTET STRING
}

BindResponse ::= SEQUENCE {
    resultCode      ENUMERATED {
        success(0),
        operationsError(1),
        protocolError(2)
    },
    matchedDN       LDAPDN,
    diagnosticMessage LDAPString
}

SearchRequest ::= SEQUENCE {
    baseObject      LDAPDN,
    scope           ENUMERATED {
        baseObject(0),
        singleLevel(1),
        wholeSubtree(2)
    },
    derefAliases    ENUMERATED {
        neverDerefAliases(0),
        derefInSearching(1),
        derefFindingBaseObj(2),
        derefAlways(3)
    },
    sizeLimit       INTEGER,
    timeLimit       INTEGER,
    typesOnly       BOOLEAN,
    filter          OCTET STRING,
    attributes      SEQUENCE OF AttributeName
}

LDAPMessage ::= SEQUENCE {
    messageID       MessageID,
    protocolOp      OCTET STRING,
    controls        SEQUENCE OF OCTET STRING OPTIONAL
}

END;
